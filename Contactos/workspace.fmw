FME workspace workspace.fmw

Parameters:
- SourceDataset_XLSXR = \\192.168.1.83\Mercadeo\CONTACTOS\X REVISAR\DEPURADOS\ContactosCumbre (26 de diciembre 2019).xlsx   # Source Microsoft Excel File(s)
- SourceDataset_XLSXR_5 = \\192.168.1.83\Representaciones\FME\PROYECTOS\FME Geo Oil Energy\DATOS\todoscontactos.xlsx   # Source Microsoft Excel File(s)
- DestDataset_XLSXW = \\192.168.1.83\Representaciones\FME\PROYECTOS\FME Geo Oil Energy\DATOS\geoilenergydb.xlsx   # Destination Microsoft Excel File
- DestDataset_XLSXW_5 = \\192.168.1.83\Representaciones\FME\PROYECTOS\FME Geo Oil Energy\DATOS\geoilenergydb.xlsx   # Destination Microsoft Excel File

Readers:
- XLSXR_1: XLSXR from $(SourceDataset_XLSXR)
- XLSXR_2: XLSXR from $(SourceDataset_XLSXR_5)

Writers:
- XLSXW_1: XLSXW to $(DestDataset_XLSXW)
- XLSXW_2: XLSXW to $(DestDataset_XLSXW_5)

Bookmark: Reader
Hoja1 (reader XLSXR_2)
    attributes: categoria char(720), nombre completo char(36), nombre string, apellido string, correo char(69), correo_personal string, correo_corporativo string, telefono char(86), cargo char(90), observaciones char(329), empresa char(481), nit number(11,0), empresa_tipo char(83), ubicación_geografica char(24), direccion char(93), bluemarble number(2,0)
    -> Sampler
Creator
    GEOMTYPE = Geometry Object
    NUM = 1
    CREATED -> FeatureReader [INITIATOR]
Note: Leer la base de Datos inicial
FeatureReader
    ATTRIBUTES = contactos,"id,nombre,apellido,telefono,cargo,correo_personal,correo_corporativo,observaciones,empresa_id"
    ATTR_ACCUM_MODE = Only Use Result
    COMBINE_GEOM = Use Result
    DATASET = \\192.168.1.83\Representaciones\FME\PROYECTOS\FME Geo Oil Energy\DATOS\geoilenergydb.xlsx
    FORMAT = XLSXR
    INTERACT = <No Spatial Filter>
    OUTPUT_FEATURES_DISPLAY = Schema and Data Features
    XLSXR_ALLOW_DOLLAR_SIGNS = YES
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_SCAN_SCHEMA_IF_DYNAMIC = No
    XLSXR_SCHEMA = contactos,0,id,string,,,,1,nombre,char,23,,,2,apellido,char,19,,,3,telefono,char,17,,,4,cargo,char,48,,,5,correo_personal,char,46,,,6,correo_corporativo,char,57,,,7,observaciones,string,,,,8,empresa_id,number,4,0,,1,,,,NO,NO,1,,"0,0,8,465",empresas,NO,NO
    XLSXR_STRIP_SHEETNAME_SPACES = YES
    XLSXR_TABLELIST = contactos
    XLSXR_USE_SCHEMA_OTHER_FILES = No
    contactos -> TestFilter_2

Bookmark: Datos de Muestra Contactos
Sampler
    RATE = 9
    SAMPLE_MODE = No
    SAMPLE_TYPE_LONG = Every Nth Feature
    SAMPLED -> TestCorreo

Bookmark: Validacion de dato de comparación CORREO
Note: Verificar los campos de Correo de la fuente de datos
TestCorreo: TestFilter
    DEFAULT_VALUE = SIN CORREO
    TEST_LIST:
      "BOOL_OP,AND,COMPOSITE_TEST,""""""1 AND 2 AND 3 AND 4"""""",TEST_CLAUSE,TEST correo ATTRIBUTE_HAS_A_VALUE ""
      CASE_INSENSITIVE_TEST @Value(correo) CONTAINS @
      TEST correo_laboral NOT_ATTRIBUTE_HAS_A_VALUE ""
      TEST correo_personal NOT_ATTRIBUTE_HAS_A_VALUE """,Correo,"BOOL_OP,COMPOSITE,COMPOSITE_TEST,""""""1 AND ( 2 OR 3 )"""""",TEST_CLAUSE,TEST correo NOT_ATTRIBUTE_HAS_A_VALUE ""
      TEST correo_laboral ATTRIBUTE_HAS_A_VALUE ""
      TEST correo_corporativo ATTRIBUTE_HAS_A_VALUE """,Correo Personal y Corporativo,"BOOL_OP,AND,COMPOSITE_TEST,""""""1 AND 2 AND 3"""""",TEST_CLAUSE,TEST correo ATTRIBUTE_HAS_A_VALUE ""
      TEST correo_laboral ATTRIBUTE_HAS_A_VALUE ""
      TEST correo_personal ATTRIBUTE_HAS_A_VALUE """,Tiene 3 Correos
    Correo -> CorreosDuplicados
Note: Eliminar los datos Duplicados
CorreosDuplicados: DuplicateFilter
    INPUT_ORDERED_CHOICE = No
    KEYATTR = correo
    UNIQUE -> AsignarCorreos
Note: Asignar los valores correspondientes a correo_personal y correo_corporativo
AsignarCorreos: AttributeManager
    ATTR_TABLE:
      SET_TO correo_personal = FME_CONDITIONAL:DEFAULT_VALUE'FME_NULL_VALUE'BOOL_OP;OR;COMPOSITE_TEST;1 OR 2 OR 3;CASE_INSENSITIVE_TEST @Value(correo) CONTAINS_REGEX .@gmail.com;CASE_INSENSITIVE_TEST @Value(correo) CONTAINS_REGEX .@hotmail.com;CASE_INSENSITIVE_TEST @Value(correo) CONTAINS_REGEX .@yahoo'@LowerCase(@Value(correo))'FME_NUM_CONDITIONS2___
      SET_TO correo_corporativo = FME_CONDITIONAL:DEFAULT_VALUE'FME_NULL_VALUE'BOOL_OP;AND;COMPOSITE_TEST;1 AND 2 AND 3;CASE_INSENSITIVE_TEST @Value(correo) NOT_CONTAINS_REGEX .@gmail.com;CASE_INSENSITIVE_TEST @Value(correo) NOT_CONTAINS_REGEX .@hotmail.com;CASE_INSENSITIVE_TEST @Value(correo) NOT_CONTAINS_REGEX .@yahoo'@LowerCase(@Value(correo))'FME_NUM_CONDITIONS2___
    -> EliminarAttrCorreo
Note: Eliminar el atributo no necesario - Correo
EliminarAttrCorreo: AttributeRemover
    REMOVE_ATTRS = correo
    -> TestFilter_3

Bookmark: Verificar SI el CONTACTO ya existe en la base de datos
Note: Separar los correos de entrada por Tipo
TestFilter_3
    DEFAULT_VALUE = Sin correo
    TEST_LIST = "BOOL_OP,AND,COMPOSITE_TEST,""""""1"""""",TEST_CLAUSE,TEST correo_corporativo ATTRIBUTE_HAS_A_VALUE """,correo_corporativo,"BOOL_OP,AND,COMPOSITE_TEST,""""""1"""""",TEST_CLAUSE,TEST correo_personal ATTRIBUTE_HAS_A_VALUE """,correo_personal
    correo_corporativo -> FeatureJoiner_3 [LEFT]
    correo_personal -> FeatureJoiner_4 [LEFT]
Note: Separar los correos de la db por Tipo
TestFilter_2
    DEFAULT_VALUE = Sin correo
    TEST_LIST = "BOOL_OP,AND,COMPOSITE_TEST,""""""1"""""",TEST_CLAUSE,TEST correo_corporativo ATTRIBUTE_HAS_A_VALUE """,correo_corporativo,"BOOL_OP,AND,COMPOSITE_TEST,""""""1"""""",TEST_CLAUSE,TEST correo_personal ATTRIBUTE_HAS_A_VALUE """,correo_personal
    correo_personal -> FeatureJoiner_4 [RIGHT]
    correo_corporativo -> FeatureJoiner_3 [RIGHT]
Note: Comparación entre correos Corporativos
FeatureJoiner_3
    ATTR_CONFLICT_RES = Use Left
    GEOMETRY_HANDLING = Use Left
    JOIN_KEYS = correo_corporativo correo_corporativo STRING
    JOIN_MODE = Inner
    UNJOINED_LEFT -> Junction
Note: Comparaicón entre Correos Personales
FeatureJoiner_4
    ATTR_CONFLICT_RES = Use Left
    GEOMETRY_HANDLING = Use Left
    JOIN_KEYS = correo_personal correo_personal AUTO
    JOIN_MODE = Inner
    UNJOINED_LEFT -> Junction
Note: Contactos por agregar en bd general
Junction
    -> TestNombre

Bookmark: Normalizar los datos para tabla CONTACTOS
TestNombre: TestFilter
    DEFAULT_VALUE = <UNFILTERED>
    TEST_LIST:
      "BOOL_OP,COMPOSITE,COMPOSITE_TEST,""""""1 AND (NOT 2 AND 3 )"""""",TEST_CLAUSE,TEST nombre completo ATTRIBUTE_HAS_A_VALUE ""
      TEST nombre ATTRIBUTE_HAS_A_VALUE ""
      TEST apellido NOT_ATTRIBUTE_HAS_A_VALUE """,NOMBRE COMPLETO
    NOMBRE COMPLETO -> Separar_Nombre
Note: Separar el nombre
Separar_Nombre: AttributeSplitter
    ATTR_NAME = nombre completo
    DELIMITER = " "
    DROP_EMPTY_PARTS = No
    LIST_NAME = _list
    TRIM_OPTION = Both
    -> Contar_Palabras_Nombre
Note: Conocer la cantidad de palabras del nombre
Contar_Palabras_Nombre: ListElementCounter
    CNT_ATTR = _element_count
    LIST_NAME = _list{}
    -> Asignar_Nombre_y_Apellido
Note: Asignar el nombre y apellido a los atributos correspondientes y borrar los atributos que ya no son necesarios
Asignar_Nombre_y_Apellido: AttributeManager
    ATTR_TABLE:
      SET_TO nombre = FME_CONDITIONAL:DEFAULT_VALUE'_FME_NO_OP_'BOOL_OP;OR;COMPOSITE_TEST;1;TEST @Value(_element_count) = 0''BOOL_OP;OR;COMPOSITE_TEST;1 OR 2;TEST @Value(_element_count) = 1;TEST @Value(_element_count) = 2'@Value(_list{0})'BOOL_OP;OR;COMPOSITE_TEST;1 OR 2;TEST @Value(_element_count) = 3;TEST @Value(_element_count) = 4'@Value(_list{0}) @Value(_list{1})'BOOL_OP;OR;COMPOSITE_TEST;1 OR 2;TEST @Value(_element_count) = 5;TEST @Value(_element_count) = 6'@Value(_list{0}) @Value(_list{1}) @Value(_list{2})'FME_NUM_CONDITIONS5___
      SET_TO apellido = FME_CONDITIONAL:DEFAULT_VALUE'_FME_NO_OP_'BOOL_OP;OR;COMPOSITE_TEST;1 OR 2;TEST @Value(_element_count) = 0;TEST @Value(_element_count) = 1''BOOL_OP;OR;COMPOSITE_TEST;1;TEST @Value(_element_count) = 2'@Value(_list{1})'BOOL_OP;OR;COMPOSITE_TEST;1;TEST @Value(_element_count) = 3'@Value(_list{2})'BOOL_OP;OR;COMPOSITE_TEST;1;TEST @Value(_element_count) = 4'@Value(_list{2}) @Value(_list{3})'BOOL_OP;OR;COMPOSITE_TEST;1;TEST @Value(_element_count) = 5'@Value(_list{3}) @Value(_list{4})'BOOL_OP;OR;COMPOSITE_TEST;1;TEST @Value(_element_count) = 6'@Value(_list{2}) @Value(_list{3}) @Value(_list{4})'FME_NUM_CONDITIONS7___
      REMOVE _list{}
      REMOVE _element_count
      SET_TO nombre = @TitleCase(@Value(nombre))
      SET_TO apellido = @TitleCase(@Value(apellido))
      SET_TO empresa = @UpperCase(@Value(empresa))
    -> AttributeRemover
Note: Elimanr attr innecesario - Nombre
AttributeRemover
    REMOVE_ATTRS = nombre completo
    -> Tester_4

Bookmark: Normalización de Empresa_id para la tabla de CONTACTOS
Note: Verificar si el contacto esta asociado a una empresa
Tester_4
    BOOL_OP = AND
    COMPOSITE_TEST = 1 AND 2 AND 3
    TEST_CLAUSE:
      CASE_INSENSITIVE_TEST empresa ATTRIBUTE_HAS_A_VALUE ""
      CASE_INSENSITIVE_TEST @Value(empresa) NOT_= null
      CASE_INSENSITIVE_TEST @Value(empresa) NOT_=
    TEST_MODE = CASE_INSENSITIVE_TEST
    PASSED -> FeatureJoiner [LEFT]
Creator_2
    GEOMTYPE = Geometry Object
    NUM = 1
    CREATED -> FeatureReader_3 [INITIATOR]
Note: Leer las Empresas que ya se encuentran en la Base de DATOS
FeatureReader_3
    ATTRIBUTES = empresas,"id,nombre,sigla,pagina_web,nit,logo,direccion"
    ATTR_ACCUM_MODE = Only Use Result
    COMBINE_GEOM = Use Result
    DATASET = \\192.168.1.83\Representaciones\FME\PROYECTOS\FME Geo Oil Energy\DATOS\geoilenergydb.xlsx
    FORMAT = XLSXR
    INTERACT = <No Spatial Filter>
    OUTPUT_FEATURES_DISPLAY = Schema and Data Features
    XLSXR_ALLOW_DOLLAR_SIGNS = YES
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_SCAN_SCHEMA_IF_DYNAMIC = No
    XLSXR_SCHEMA = empresas,0,id,number,4,0,,1,nombre,char,68,,,2,sigla,char,1,,,3,pagina_web,char,1,,,4,nit,char,1,,,5,logo,char,1,,,6,direccion,char,1,,,1,,,,NO,NO,1,,"0,0,6,352",contactos,NO,NO
    XLSXR_STRIP_SHEETNAME_SPACES = YES
    XLSXR_TABLELIST = empresas
    XLSXR_USE_SCHEMA_OTHER_FILES = No
    empresas -> FeatureJoiner [RIGHT]
    empresas -> StatisticsCalculator_2
Note: Comparar lios datos de entrada con la base de datos para saber si la empresa ya existe
FeatureJoiner
    ATTR_CONFLICT_RES = Use Left
    GEOMETRY_HANDLING = Use Left
    JOIN_KEYS = empresa nombre STRING
    JOIN_MODE = Inner
    JOINED -> AttributeRenamer
    UNJOINED_LEFT -> DuplicateFilter

Bookmark: Crear Nuevas Empresas
Note: Conecer el ultimo valor del id empresa para asignación
StatisticsCalculator_2
    COMPUTE_HISTOGRAM = NO
    MAX_ATTR = _max
    PREPEND_ATTR_NAME_CHOICE = For multiple results only
    STATS_ATTRS = id
    SUMMARY -> Counter
Note: Remover los nombres de las Empresas duplicados
DuplicateFilter
    INPUT_ORDERED_CHOICE = No
    KEYATTR = empresa
    UNIQUE -> Counter
Note: A partir del id de la base de datos, asignar valores del id a las nuevas Empresas
Counter
    CNT_ATTR = id
    DOMAIN = counter
    SCOPE = Local
    START = @Value(_max)
    -> Tester
Tester
    BOOL_OP = OR
    COMPOSITE_TEST = 1
    TEST_CLAUSE = TEST @Value(id) != @Value(_max)
    TEST_MODE = TEST
    PASSED -> AttributeRenamer

Bookmark: Agregar CONTACTOS a la base de datos
AttributeRenamer
    ATTR_TABLE = RENAME_SET_DEFAULT id > empresa_id
    -> AttributeManager
AttributeManager
    ATTR_TABLE:
      SET_TO id = FME_NULL_VALUE
      SET_TO telefono = FME_CONDITIONAL:DEFAULT_VALUE'FME_NULL_VALUE'BOOL_OP;OR;COMPOSITE_TEST;1;TEST telefono ATTRIBUTE_HAS_A_VALUE _FME_BLANK_STRING_'@Value(telefono)'FME_NUM_CONDITIONS2___
      SET_TO cargo = FME_CONDITIONAL:DEFAULT_VALUE'FME_NULL_VALUE'BOOL_OP;OR;COMPOSITE_TEST;1;TEST cargo ATTRIBUTE_HAS_A_VALUE _FME_BLANK_STRING_'@Value(cargo)'FME_NUM_CONDITIONS2___
      SET_TO observaciones = FME_CONDITIONAL:DEFAULT_VALUE'FME_NULL_VALUE'BOOL_OP;OR;COMPOSITE_TEST;1;TEST observaciones ATTRIBUTE_HAS_A_VALUE _FME_BLANK_STRING_'@Value(observaciones)'FME_NUM_CONDITIONS2___
      REMOVE empresa
      REMOVE categoria
      REMOVE nit
      REMOVE empresa_tipo
      REMOVE ubicación_geografica
      REMOVE direccion
      REMOVE bluemarble
      REMOVE sigla
      REMOVE pagina_web
      REMOVE logo
      REMOVE _max
    -> contactos (writer XLSXW_2)
contactos (writer XLSXW_2) [off]
    attributes: id auto(20), nombre string(20), apellido string(20), telefono string(86), cargo string(90), correo_personal string(20), correo_corporativo string(20), observaciones string(329), empresa_id auto(20)
